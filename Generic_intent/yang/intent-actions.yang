//-------------------------------------------------------------------------------------
// Copyright (c) 2021-2022
//-------------------------------------------------------------------------------------
module intent-actions {
    namespace "urn:icanlab:intent:actions";
    prefix "intent-actions";

    revision 2021-08-22 {
        description "Initial revision";
    }

    grouping action {
        description "The action (verb) of what is to be performed by this intent.";
    }

    grouping allow {
        uses action;
        description "Indicates traffic is allowed.";
    }

    grouping block {
        uses action;
        description "Indicates traffic is not allowed";
    }

    grouping redirect {
        uses action;
        description "Indicates traffic is to redirect";
        leaf service-name {
            type string;
            description "Service name to redirect the flow.";
        }
    }

    grouping mirror {
        uses action;
        description "Indicates traffic is copied to other virtual port";
        leaf destination {
            type string;
            description "Name of the recipient.";
        }
    }

    grouping log {
        uses action;
        description "Indicates log in the traffic";
    }

    grouping should-enter {
        uses action;
        description "Indicates traffic should enter to a given device.";
    }

    grouping should-exit {
        uses action;
        description "Indicates traffic should exit from a given device.";
    }
}
